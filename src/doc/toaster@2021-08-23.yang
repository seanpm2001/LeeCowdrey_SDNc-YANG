module toaster {
  yang-version 1.1;
  namespace "http://netconfcentral.org/ns/toaster";
  prefix toast;

  import sdnc {
    prefix c;
    revision-date 2020-12-04;
  }
  import sdnc-sku {
    prefix cs;
    revision-date 2020-12-04;
  }
  import sdnc-xnf {
    prefix cnf;
    revision-date 2020-12-04;
  }
  import ietf-inet-types {
    prefix inet;
    revision-date 2013-05-15;
    reference
      "RGC 6991";
  }

  organization
    "Netconf Central";
  contact
    "Andy Bierman <andy@netconfcentral.org>";
  description
    "YANG version of the TOASTER-MIB.

     Copyright (c) 2009 Andy Bierman and the persons identified as
     authors of the code.  All rights reserved.

     Redistribution and use in source and binary forms, with or
     without modification, is permitted pursuant to, and subject
     to the license terms contained in, the BSD 3-Clause License
     http://opensource.org/licenses/BSD-3-Clause";

  revision 2021-08-23 {
    description
      "Toaster module modified to include CSDM yang-to-cli
       extension while maintaining the theme of talkie the
       toaster";
  }
  revision 2009-11-20 {
    description
      "Toaster module in progress.";
  }

  identity toast-type {
    description
      "Base for all bread types supported by the toaster.
         New bread types not listed here nay be added in the
         future.";
  }

  identity white-bread {
    base toast:toast-type;
    description
      "White bread.";
  }

  identity wheat-bread {
    base toast-type;
    description
      "Wheat bread.";
  }

  identity wonder-bread {
    base toast-type;
    description
      "Wonder bread.";
  }

  identity frozen-waffle {
    base toast-type;
    description
      "Frozen waffle.";
  }

  identity frozen-bagel {
    base toast-type;
    description
      "Frozen bagel.";
  }

  identity hash-brown {
    base toast-type;
    description
      "Hash browned potatos.";
  }

  typedef DisplayString {
    type string {
      length "0 .. 255";
    }
    description
      "YANG version of the SMIv2 DisplayString TEXTUAL-CONVENTION.";
    reference
      "RFC 2579, section 2.";
  }

  container toaster {
    presence "Indicates the toaster service is available";
    description
      "Top-level container for all toaster database objects.";
    leaf toasterManufacturer {
      type DisplayString;
      config false;
      mandatory true;
      description
        "The name of the toaster's manufacturer. For instance,
              Microsoft Toaster.";
    }
    leaf toasterModelNumber {
      type DisplayString;
      config false;
      mandatory true;
      description
        "The name of the toaster's model. For instance,
             Radiant Automatic.";
    }
    leaf toasterStatus {
      type enumeration {
        enum up {
          value 1;
          description
            "The toaster knob position is up.
                    No toast is being made now.";
        }
        enum down {
          value 2;
          description
            "The toaster knob position is down.
                    Toast is being made now.";
        }
      }
      config false;
      mandatory true;
      description
        "This variable indicates the current state of
             the toaster.";
    }
  }

  augment "/c:sdnc/cnf:xnf/cnf:nf/cnf:configs" {
    description "YANG-to-CLI testing';
    container config {
      config true;
      leaf raw {
        type string;
      }
      container cli-header {
        config false;
        cs:cli-begin "configure";
        cs:occurrence "1";
      }
      leaf hostname {
        cs:cli-enable-cmd "toaster name \"{{.}}\"";
        cs:cli-modify-cmd "toaster name \"{{.}}\"";
        cs:cli-disable-cmd "no toaster name \"{{.}}\"";
        type inet:host;
      }
      container toasterSlots {
        container slot {
          list slots {
            cs:cli-begin "toaster slot {{./slot-id}}";
            cs:cli-end "exit";
            cs:cli-disable-cmd "no toaster slot {{./slot-id}}";
            key "slot-id";
            leaf slot-id {
              type uint8 {
                range "1..4";
              }
            }
            leaf autoclean {
              cs:cli-enable-cmd "autoclean enable";
              cs:cli-disable-cmd "autoclean disable";
              type boolean;
              default "false";
            }
          }
        }
      }
      container cli-footer {
        config false;
        cs:cli-end "end";
      }
    }
  }

  rpc make-toast {
    description
      "Make some toast.
         The toastDone notification will be sent when
         the toast is finished.
         An 'in-use' error will be returned if toast
         is already being made.
         A 'resource-denied' error will be returned
         if the toaster service is disabled.";
    input {
      leaf toasterDoneness {
        type uint32 {
          range "1 .. 10";
        }
        default "5";
        description
          "This variable controls how well-done is the
                 ensuing toast. It should be on a scale of 1 to 10.
                 Toast made at 10 generally is considered unfit
                 for human consumption; toast made at 1 is warmed
                 lightly.";
      }
      leaf toasterToastType {
        type identityref {
          base toast:toast-type;
        }
        default "wheat-bread";
        description
          "This variable informs the toaster of the type of
                 material that is being toasted. The toaster
                 uses this information, combined with
                 toasterDoneness, to compute for how
                 long the material must be toasted to achieve
                 the required doneness.";
      }
    }
  }

  rpc cancel-toast {
    description
      "Stop making toast, if any is being made.
         A 'resource-denied' error will be returned
         if the toaster service is disabled.";
  }

  notification toastDone {
    description
      "Indicates that the toast in progress has completed.";
    leaf toastStatus {
      type enumeration {
        enum done {
          value 0;
          description
            "The toast is done.";
        }
        enum cancelled {
          value 1;
          description
            "The toast was cancelled.";
        }
        enum error {
          value 2;
          description
            "The toaster service was disabled or
                   the toaster is broken.";
        }
      }
      description
        "Indicates the final toast status";
    }
  }
}
