module pon-volt-mf {
  yang-version 1.1;
  namespace "urn:com:vendor:yang:pon:volt-mf";
  prefix volt;

  import sdnc {
    prefix c;
    revision-date 2020-12-04;
  }
  import sdnc-xnf {
    prefix cnf;
    revision-date 2020-12-04;
  }
  import sdnc-types {
    prefix ct;
    revision-date 2020-12-04;
  }
  import sdnc-groupings {
    prefix cg;
    revision-date 2020-12-04;
  }
  import sdnc-extensions {
    prefix cx;
    revision-date 2020-12-04;
  }
  import ietf-yang-types {
    prefix yang;
    revision-date 2013-07-15;
    reference
      "RFC 6991";
  }
  import ietf-inet-types {
    prefix inet;
    revision-date 2013-05-15;
    reference
      "RFC 6991";
  }
  import yang-ext {
    prefix ext;
    revision-date 2013-07-09;
  }
  import network-topology {
    prefix nt;
    revision-date 2013-10-21;
  }

  organization
    "CommScope, Inc.";
  contact
    "lee.cowdrey@commscope.com";
  description
    "XGS-PON Virtual Management Funciton (volt-mf)";

  revision 2021-09-01 {
    description
      "initial";
  }

  feature pon-volt-mf {
    status current;
  }

  cx:sku-model-revision "2021-09-01";
  cx:sku-vendor "Vendor";
  cx:sku-model-family "XGSPON";
  cx:sku-model-type "VOLT-MF";
  cx:sku-firmware-name "default";
  cx:sku-firmware-version "1.0.0";
  cx:cli-process "false";

  augment "/c:sdnc/cnf:xnf/cnf:nf/cnf:configs" {
    if-feature "c:sdnc";
    if-feature "cnf:sdnc-xnf";
    container config {
      config true;
      leaf raw {
        type string;
      }
      container hardware {
        uses cg:common-hardware {
          refine "unit-name" {
            default "VOLT-MF";
            mandatory false;
          }
          refine "unit-version" {
            default "1.0";
            mandatory false;
          }
        }
      }
      leaf node-id {
        type leafref {
          path "/nt:network-topology/nt:topology/nt:node/nt:node-id";
          require-instance false;
        }
      }
    }
  }
}
