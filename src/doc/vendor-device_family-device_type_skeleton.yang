module ZZZZZZZZ {
  yang-version 1.1;
  namespace ".*";
  prefix A;

  import sdnc {
    prefix c;
    revision-date YYYY-MM-DD;
  }
  import sdnc-types {
    prefix ct;
    revision-date YYYY-MM-DD;
  }
  import sdnc-xnf {
    prefix cnf;
    revision-date YYYY-MM-DD;
  }
  import sdnc-sku {
    prefix cs;
    revision-date YYY-MM-DD;
  }
  import sdnc-groupings {
    prefix cg;
    revision-date YYY-MM-DD;
  }

  revision YYYY-MM-DD {
    description
      "initial";
  }

  cs:sku-model-revision "2021-06-01";
  cs:sku-vendor "CommScope";
  cs:sku-model-family "Ruckus ICX";
  cs:sku-model-type "ICX 7x50 Generic";
  cs:sku-firmware-name "boot";
  cs:sku-firmware-version "8.0.30";
  cs:sku-factory-enable-username "admin";
  cs:sku-factory-enable-password "admin";
  cs:sku-factory-access-username "admin";
  cs:sku-factory-access-password "admin";
  cs:sku-config-erase-cli "erase nvram";
  cs:sku-config-reset-cli "reset nvram";
  cs:sku-config-save-to-memory-cli "write memory";
  cs:sku-config-copy-to-remote "copy running config {{../config-remote-endpoint}}";
  cs:sku-config-remote-endpoint "tftp://tftp.commscope.com/path";
  cs:sku-ssh-idle-cli "ip ssh idle-timeout {{../ssh-idle-timeout-duration}}";
  cs:sku-ssh-idle-timeout-duration "360";
  cs:cli-process "true";

  augment "/c:sdnc/cnf:xnf/cnf:nf/cnf:configs" {
    if-feature "c:sdnc";
    if-feature "cnf:sdnc-xnf";
    if-feature "cs:sdnc-sku";

    container config {
      config true;
      leaf raw {
        type string;
      }
      container cli-header {
        description "this container is optional";
        cs:cli-begin "configure";
      }

      container hardware {
        uses cg:common-hardware {
          refine "unit-name" {
            default "some string(s)";
            mandatory false;
          }
          refine "unit-version" {
            default "some string(s)";
            mandatory false;
          }
        }
      }

      leaf hostname {
        description "leaf is mandatory but hx: contents will vary";
        cs:cli-enable-cmd "hostname \"{{../hostname}}\"";
        cs:cli-disable-cmd "no hostname \"{{../hostname}}\"";
        type inet:host;
      }

      container cli-footer {
        description "this container is optional";
        cs:cli-end "end";
      }
    }
  }
}
