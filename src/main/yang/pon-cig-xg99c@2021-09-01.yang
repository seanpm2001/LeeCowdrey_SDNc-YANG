module pon-cig-xg99c {
  yang-version 1.1;
  namespace "urn:com:vendor:yang:pon:cig:xg99c";
  prefix cxg99c;

  import sdnc {
    prefix c;
    revision-date 2020-12-04;
  }
  import sdnc-xnf {
    prefix cnf;
    revision-date 2020-12-04;
  }
  import sdnc-groupings {
    prefix cg;
    revision-date 2020-12-04;
  }
  import sdnc-sku {
    prefix cs;
    revision-date 2020-12-04;
  }
  import ietf-inet-types {
    prefix inet;
    revision-date 2013-05-15;
    reference
      "RFC 6991";
  }

  organization
    "Cowdrey Consulting UK";
  contact
    "lee@cowdrey.net";
  description
    "SDNc ONU - CIG XG-99C";

  revision 2021-09-01 {
    description
      "initial";
  }

  feature pon-onu {
    status current;
  }

  cs:sku-model-revision "2021-09-01";
  cs:sku-vendor "CIG";
  cs:sku-model-family "ONU";
  cs:sku-model-type "XG-99C";
  cs:sku-firmware-name "default";
  cs:sku-firmware-version "1.0.0";
  cs:cli-process "false";

  augment "/c:sdnc/cnf:xnf/cnf:nf/cnf:configs" {
    if-feature "c:sdnc";
    if-feature "cnf:sdnc-xnf";
    container config {
      config true;
      leaf raw {
        type string;
      }
      leaf hostname {
        type inet:host;
      }
      container hardware {
        uses cg:common-hardware {
          refine "unit-name" {
            default "XG-99C";
            mandatory false;
          }
          refine "unit-version" {
            default "1.0";
            mandatory false;
          }
          refine "serial-number" {
            config true;
          }
        }
        leaf vendor {
          type string {
            length "3..max";
            pattern '([A-Za-z0-9.-]+)((\s*)([A-Za-z0-9.-]*)*)';
          }
          default "VENDOR";
        }
      }
    }
  }
}
