module pon-olt {
  yang-version 1.1;
  namespace "urn:com:vendor:yang:pon:olt";
  prefix polt;

  import sdnc {
    prefix c;
    revision-date 2020-12-04;
  }
  import sdnc-xnf {
    prefix cnf;
    revision-date 2020-12-04;
  }
  import sdnc-types {
    prefix ct;
    revision-date 2020-12-04;
  }
  import sdnc-pools {
    prefix cp;
    revision-date 2020-12-04;
  }
  import sdnc-groupings {
    prefix cg;
    revision-date 2020-12-04;
  }
  import sdnc-extensions {
    prefix cx;
    revision-date 2020-12-04;
  }
  import pon-volt-mf {
    prefix volt;
    revision-date 2021-09-01;
  }
  import ietf-yang-types {
    prefix yang;
    revision-date 2013-07-15;
    reference
      "RFC 6991";
  }
  import ietf-inet-types {
    prefix inet;
    revision-date 2013-05-15;
    reference
      "RFC 6991";
  }

  organization
    "CommScope, Inc.";
  contact
    "lee.cowdrey@commscope.com";
  description
    "CSDM PON xOLT (pOLT/vOLT)

     CommScope © 2020-2021 All Rights Reserved

     This program is confidential and proprietary to CommScope, Inc.
     (CommScope), and may not be copied, reproduced, modified, disclosed
     to others, published or used, in whole or in part, without the express
     prior written permission of CommScope.
    ";

  revision 2021-09-01 {
    description
      "initial";
  }

  feature pon-olt {
    status current;
  }

  cx:sku-model-revision "2021-09-01";
  cx:sku-vendor "CommScope";
  cx:sku-model-family "XGSPON";
  cx:sku-model-type "ARRIS OLT";
  cx:sku-firmware-name "default";
  cx:sku-firmware-version "1.0.0";
  cx:cli-process "false";

  augment "/c:sdnc/cnf:xnf/cnf:nf/cnf:configs" {
    if-feature "c:sdnc";
    if-feature "cnf:sdnc-xnf";
    if-feature "cp:sdnc-pools";
    if-feature "volt:pon-volt-mf";
    container config {
      config true;
      leaf raw {
        type string;
      }
      container hardware {
        uses cg:common-hardware {
          refine "unit-name" {
            default "OLT";
            mandatory false;
          }
          refine "unit-version" {
            default "1.0.0";
            description
              "The interface-version of the device , which uniquely identifies the yang-modules set & revision supported by the device";
            mandatory false;
          }
        }
        leaf model {
          type string;
          description
            "The model of device. Identifies the hardware variant of the device.
             Example 4LT/8LT card numbers etc";
          default "standard";
        }
        list component {
          key "name";
          leaf name {
            type string;
          }
          leaf class {
            type enumeration {
              enum unknown;
              enum chassis;
              enum backplane;
              enum container;
              enum power-supply;
              enum fan;
              enum sensor;
              enum module;
              enum port;
              enum stack;
              enum cpu;
              enum energy-object;
              enum battery;
              enum storage-drive;
            }
            mandatory true;
          }
          leaf physical-index {
            type int32 {
              range "1..2147483647";
            }
          }
          leaf description {
            type string;
          }
          leaf parent {
            type leafref {
              path "../../component/name";
              require-instance false;
            }
          }
          leaf parent-rel-pos {
            type int32 {
              range "0 .. 2147483647";
            }
          }
          leaf-list contains-child {
            type leafref {
              path "../../component/name";
            }
          }
          leaf hardware-rev {
            type string;
          }
          leaf firmware-rev {
            type string;
          }
          leaf software-rev {
            type string;
          }
          leaf serial-num {
            type string;
          }
          leaf mfg-name {
            type string;
          }
          leaf model-name {
            type string;
          }
          leaf alias {
            type string;
          }
          leaf asset-id {
            type string;
          }
          leaf is-fru {
            type boolean;
          }
          leaf mfg-date {
            type yang:date-and-time;
          }
          leaf-list uri {
            type inet:uri;
          }
          leaf uuid {
            type yang:uuid;
          }
        }
      }
      container interfaces {
        list interface {
          key "name";
          leaf name {
            type string;
          }
          leaf description {
            type string;
          }
          leaf type {
            type enumeration {
              enum channel-group;
              enum channel-partition;
              enum channel-pair;
              enum channel-termination;
              enum ani;
              enum v-ani;
              enum onu-v-enet;
              enum olt-v-enet;
              enum on-v-vrefpoint;
            }
            default "channel-group";
          }
          container channel-group {
            when "../type='channel-group'";
            leaf polling-period {
              type uint32 {
                range "1..864000";
              }
              units "0.1 second";
              default "100";
            }
            leaf raman-mitigation {
              type ct:raman-mitigation-type;
              default "raman-none";
            }
            leaf system-id {
              type string {
                pattern '[0-9a-fA-F]{5}';
              }
            }
            container pon-pools {
              list pon-pool {
                key "name";
                min-elements 1;
                max-elements 8;
                leaf name {
                  type ct:string-ascii64;
                }
                leaf channel-termination-ref {
                  type ct:interface-ref;
                }
                leaf alloc-id-values {
                  type ct:alloc-id-values;
                }
                leaf gemport-values {
                  type ct:gemport-values;
                }
                leaf onu-id-values {
                  type ct:onu-id-values;
                }
              }
            }
          }
          container channel-paritition {
            when "../type='channel-partition'";
          }
          container channel-pair {
            when "../type='channel-pair'";
          }
          container channel-termination {
            when "../type='channel-termination'";
          }
          container ani {
            when "../type='ani'";
          }
          container v-ani {
            when "../type='v-ani'";
          }
          container onu-v-enet {
            when "../type='onu-v-enet'";
          }
          container olt-v-enet {
            when "../type='olt-v-enet'";
          }
          container on-v-vrefpoint {
            when "../type='on-v-vrefpoint'";
          }
          leaf enabled {
            type boolean;
            default "true";
          }
        }
      }
      leaf vendor {
        type string {
          length "3..max";
          pattern '([A-Za-z0-9.-]+)((\s*)([A-Za-z0-9.-]*)*)';
        }
        default "COMMSCOPE";
      }
      leaf push-pma-configuration-to-device {
        type boolean;
        default "true";
      }
      leaf connection-model {
        type enumeration {
          enum call-home;
          enum direct;
          enum snmp;
          enum mediated-session;
        }
        default "direct";
      }
      container collection {
        leaf traffic-descriptor-profile {
          type leafref {
            path "/c:sdnc/cp:pools/cp:pon/cp:collection/cp:traffic-descriptors/cp:name";
            require-instance true;
          }
        }
        leaf l2-dhcp4-relay-profile {
          type leafref {
            path "/c:sdnc/cp:pools/cp:pon/cp:collection/cp:l2-dhcp4-relays/cp:name";
            require-instance true;
          }
        }
        leaf qos-policy {
          type leafref {
            path "/c:sdnc/cp:pools/cp:pon/cp:collection/cp:qos-policies/cp:name";
            require-instance true;
          }
        }
        leaf qos-classifier {
          type leafref {
            path "/c:sdnc/cp:pools/cp:pon/cp:collection/cp:qos-classifiers/cp:name";
            require-instance true;
          }
        }
        leaf remote-endpoint {
          type leafref {
            path "/c:sdnc/cp:pools/cp:pon/cp:collection/cp:remote-endpoints/cp:name";
            require-instance true;
          }
        }
      }
    }
  }
}
